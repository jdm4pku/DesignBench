package 'Car Mass Rollup Example 1' {
	private import ScalarValues::*;
	private import MassRollup1::*;
	part def CarPart :> MassedThing {			
		attribute serialNumber: String;
	}
	part car: CarPart :> compositeThing {	
		attribute vin :>> serialNumber;
		part carParts: CarPart[*] :>> subcomponents;
		part engine :> simpleThing, carParts {
			//...
		}
		part transmission :> simpleThing, carParts {
			//...
		}
	}
	private import SI::kg;
	part c :> car {
		attribute :>> simpleMass = 1000[kg];
		part :>> engine {
			attribute :>> simpleMass = 100[kg];
		}
		part redefines transmission {
			attribute :>> simpleMass = 50[kg];
		}	
	}
	// c::totalMass --> 1150.0[kg]
}
