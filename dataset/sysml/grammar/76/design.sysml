package 'Verification Case Usage Example' {
	private import 'Verification Case Definition Example'::*;
	part def MassVerificationSystem;
	part def Scale;
	part vehicleTestConfig : Vehicle {
		// ...
	}
	verification vehicleMassTest : VehicleMassTest {
		subject testVehicle :> vehicleTestConfig;
	}
	part massVerificationSystem : MassVerificationSystem {
		perform vehicleMassTest;	
		part scale : Scale {
			perform vehicleMassTest.collectData {
				in part :>> testVehicle;
				// In reality, this would be some more involved process.
				measurement = testVehicle.mass;
				out :>> massMeasured = measurement;
			}
		}
	}		
	individual def TestSystem :> MassVerificationSystem;
	individual def TestVehicle1 :> Vehicle;
	individual def TestVehicle2 :> Vehicle;
	individual testSystem : TestSystem :> massVerificationSystem {
		timeslice test1 {
			perform action :>> vehicleMassTest {
				in individual :>> testVehicle : TestVehicle1 {
					:>> mass = 2500[SI::kg];
				}
			}
		}
		then timeslice test2 {
			perform action :>> vehicleMassTest {
				in individual :>> testVehicle : TestVehicle2 {
					:>> mass = 3000[SI::kg];
				}
			}
		}
	}
}
