package 'Control Structures Example' {
	private import ScalarValues::*;
	attribute def BatteryCharged;
	part battery;
	part powerSystem;
	action def MonitorBattery { out charge : Real; }
	action def AddCharge { in charge : Real; }
	action def EndCharging;
	action def ChargeBattery {
		loop action charging {
			action monitor : MonitorBattery {
				out charge;
			}
			then if monitor.charge < 100 {
				action addCharge : AddCharge {
					in charge = monitor.charge;
				}
			}				
		} until charging.monitor.charge >= 100;
		then action endCharging : EndCharging;
		then done;
	}
}
