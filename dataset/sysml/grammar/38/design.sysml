package 'VehiclePowerManagement' {
	attribute def VehicleStartSignal;
	attribute def VehicleOnSignal;
	attribute def VehicleOffSignal;
	state def VehicleStates;
	state vehicleStates : VehicleStates {
		entry; then off;
		state off;
		accept VehicleStartSignal 
			then starting;
		state starting;
		accept VehicleOnSignal
			then on;
		state on;
		accept VehicleOffSignal
			then off;
	}
}
