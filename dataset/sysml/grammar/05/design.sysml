package 'TrafficLightDefinition' {
	private import ScalarValues::Real;
	enum def TrafficLightColor {
		enum green;
		enum yellow;
		enum red;
	}
	part def TrafficLight {
		attribute currentColor : TrafficLightColor;
	}
	part def TrafficLightGo specializes TrafficLight {
		attribute redefines currentColor = TrafficLightColor::green;
	}
}
