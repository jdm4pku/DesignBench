package 'FuelFlowManagement' {
	attribute def Temp;
	part def Fuel;
	port def FuelPort {
		attribute temperature : Temp;
		out item fuelSupply : Fuel;
		in item fuelReturn : Fuel;
	}
	part def FuelTank {
		port fuelTankPort : FuelPort;
	}
	part def Engine {
		port engineFuelPort : ~FuelPort;
	}
}
