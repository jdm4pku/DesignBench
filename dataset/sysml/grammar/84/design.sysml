package 'Allocation Usage Example' {
	package LogicalModel {
		action def ProvidePower;
		action def GenerateTorque;
		part def TorqueGenerator;
		action providePower : ProvidePower {
			action generateTorque : GenerateTorque;
		}
		part torqueGenerator : TorqueGenerator {
			perform providePower.generateTorque;
		}
	}
	package PhysicalModel {
		private import LogicalModel::*;
		part def PowerTrain;
		part def Engine;
		part powerTrain : PowerTrain {
			part engine : Engine {
				perform providePower.generateTorque;
			}
		}
		allocate torqueGenerator to powerTrain {
			allocate torqueGenerator.generateTorque to powerTrain.engine.generateTorque;
		}
	}
}
