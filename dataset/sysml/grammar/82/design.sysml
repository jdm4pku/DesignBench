package 'SoftwareHardwareDependencies' {
	part 'System Assembly' {
		part 'Computer Subsystem' {
			// ...
		}
		part 'Storage Subsystem' {
			// ...
		}
	}
	package 'Software Design' {
		item def MessageSchema {
			// ...
		}
		item def DataSchema {
			// ...
		}
	}
	dependency from 'System Assembly'::'Computer Subsystem' to 'Software Design';
	dependency Schemata 
		from 'System Assembly'::'Storage Subsystem' 
		to 'Software Design'::MessageSchema, 'Software Design'::DataSchema;
}
