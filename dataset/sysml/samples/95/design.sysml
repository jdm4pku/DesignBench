package 'AutomotiveDocumentation' {
	doc /* This is documentation of the owning 
	     * package.
	     */
	part def Automobile {
		doc Document1 /* This documentation of Automobile. */
	}
	alias Car for Automobile {
		doc /* This is documentation of the alias. */
	}
	alias Torque for ISQ::TorqueValue;
}
