library package 'RiskandFailureModelingLibrary' {
	private import ScalarValues::Real;
	private import RiskMetadata::Level;
	abstract occurrence def Situation;
	abstract occurrence situations : Situation[*] nonunique;
	abstract occurrence def Cause {
		attribute probability : Real;
	}
	abstract occurrence causes : Cause[*] nonunique :> situations;
	abstract occurrence def Failure {
		attribute severity : Level;
	}
	abstract occurrence failures : Failure[*] nonunique :> situations;
	abstract connection def Causation :> Occurrences::HappensBefore {
		end cause : Situation[*];
		end effect : Situation[*];
	}
	abstract connection causations : Causation[*] nonunique;
	item def Scenario {
		occurrence :>> situations;
		occurrence :>> causes :> situations;
		occurrence :>> failures :> situations;
	}
	item scenarios : Scenario[*] nonunique;
}
