package 'Automotive Domain Annotations' {
	/* This is a comment, which is a part of the model, 
	 * annotating (by default) it's owning namespace. */
	comment Comment1 /* This is a named comment. */
	comment about Automobile
	/* This is an unnamed comment, annotating an 
	 * explicitly specified element. 
	 */
	part def Automobile;
	alias Car for Automobile {
		/*
		 * This is a comment annotating its owning
		 * element.
		 */
	}	                         
	// This is a note. It is in the text, but not part 
	// of the model.
	alias Torque for ISQ::TorqueValue;
}
