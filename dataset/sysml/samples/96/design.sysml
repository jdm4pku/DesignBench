package 'ImportPackageExercise' {
	public import ISQ::TorqueValue;
	private import ScalarValues::*;
	private part def Automobile;
	public alias Car for Automobile;	                         
	alias Torque for ISQ::TorqueValue;
}
