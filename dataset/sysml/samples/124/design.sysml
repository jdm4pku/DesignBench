package 'VehicleArchitectureStructuralViewpoint' {
	package SystemModel {
		private import SI::*;
		part def Vehicle;
		part def AxleAssembly;
		part def Axle;
		part def Wheel;
		part vehicle : Vehicle {
			attribute mass :> ISQ::mass = 2500[SI::kg];
			part frontAxleAssembly : AxleAssembly[1] {
				attribute mass :> ISQ::mass = 150[kg];
				part frontWheel : Wheel[2];
				part frontAxle : Axle[1] {
					attribute mass;
					attribute steeringAngle;
				}
			}
			part rearAxleAssembly : AxleAssembly[1] {
				attribute mass :> ISQ::mass = 250[kg];
				part rearWheel : Wheel[2];
				part rearAxle : Axle[1] {
					attribute mass;
				}
			}
		}
	}
	package ViewModel {
		private import Views::*;
		part 'systems engineer';
		concern 'system breakdown' {
			stakeholder :>> 'systems engineer';
		}
		viewpoint 'system structure perspective' {		
			frame 'system breakdown';
		}
		view 'system structure generation' {
			satisfy 'system structure perspective';
			expose SystemModel::vehicle::**[@SysML::PartUsage];
			render asElementTable {
				view :>> columnView[1] {
					render asTextualNotation;
				}
			}
		}
	}
}
