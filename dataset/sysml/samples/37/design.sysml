package 'VehiclePowerManagement' {
	attribute def VehicleStartSignal;
	attribute def VehicleOnSignal;
	attribute def VehicleOffSignal;
	part def Vehicle;
	action performSelfTest { in vehicle : Vehicle; }
	state def VehicleStates { in operatingVehicle : Vehicle; }
	state vehicleStates : VehicleStates {
		in operatingVehicle : Vehicle;
		entry; then off;
		state off;
		accept VehicleStartSignal 
			then starting;
		state starting;
		accept VehicleOnSignal
			then on;
		state on {
			entry performSelfTest{ in vehicle = operatingVehicle; }
			do action providePower { /* ... */ }
			exit action applyParkingBrake { /* ... */ }
		}
		accept VehicleOffSignal
			then off;
	}	
}
