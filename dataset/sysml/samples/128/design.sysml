package 'PowertrainFunctiontoComponentMapping' {
	private import LogicalModel::*;
	private import PhysicalModel::*;
	package LogicalModel {
		action providePower {
			action generateTorque;
		}
		part torqueGenerator {
			perform providePower.generateTorque;
		}
	}
	package PhysicalModel {
		part powerTrain {
			part engine {
				perform providePower.generateTorque;
			}
		}
	}
	allocate torqueGenerator to powerTrain {
		allocate torqueGenerator.generateTorque to powerTrain.engine.generateTorque;
	}
}
