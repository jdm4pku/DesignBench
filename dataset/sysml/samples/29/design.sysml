package Camera {
	private import 'Action Decomposition'::*;
	part def Scene;
	part def Image;
	part def Picture;
	part def Camera;
	part def FocusingSubsystem;
	part def ImagingSubsystem;
	part camera : Camera {
		ref item scene : Scene;
		part photos : Picture[*];
		part autoFocus {
			in ref item scene : Scene = camera::scene;		
			out ref item realImage : Image;
		}
		flow autoFocus.realImage to imager.focusedImage;
		part imager {
			in item focusedImage : Image;		
			out item photo : Picture :> photos;
		}
	}
}
