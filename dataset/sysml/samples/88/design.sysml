package 'VehicleSafetyCompliance' {
	private import ScalarValues::Boolean;
	metadata def Safety {
		attribute isMandatory : Boolean;
	}
	part vehicle {
		part interior {
			part alarm;
			part seatBelt[2] {@Safety{isMandatory = true;}}
			part frontSeat[2];
			part driverAirBag {@Safety{isMandatory = false;}}
		}
		part bodyAssy {
			part body;
			part bumper {@Safety{isMandatory = true;}}
			part keylessEntry;
		}
		part wheelAssy {
			part wheel[2];
			part antilockBrakes[2] {@Safety{isMandatory = false;}}
		}
	}
	package 'Safety Features' {
		/* Parts that contribute to safety. */		
		private import vehicle::**[@Safety];
	}
	package 'Mandatory Safety Features' {
		/* Parts that contribute to safety AND are mandatory. */
		private import vehicle::**[@Safety and Safety::isMandatory];
	}
}
